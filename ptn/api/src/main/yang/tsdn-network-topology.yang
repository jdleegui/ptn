module tsdn-network-topology  {
    yang-version 1;
    namespace "urn:opendaylight:params:xml:ns:yang:tsdn-network-topology";
    prefix "tnt";

    import ietf-inet-types { prefix "inet"; revision-date 2013-07-15; }
    import tsdn-port {prefix tport; revision-date "2015-01-05";}
    import tsdn-node {prefix tnode; revision-date "2015-01-05";}
    import tsdn-general-types {prefix ttypes; revision-date "2015-01-05";}
    import tsdn-tunnel {prefix "ttunnel"; revision-date "2015-01-05"; }
    import tsdn-tunnel-xc {prefix "ttunnelxc"; revision-date "2015-01-05"; }
    
    
    revision 2015-01-05 {
        description
            "Initial revision.";
    }

    typedef node-connector-leafref {
        type leafref {
            path "/network-topology/topology/node/node-connector/node-connector-id";
        }
        description
            "A type for an absolute reference to a termination point.";
    }
    typedef topology-leafref {
        type leafref {
            path "/network-topology/topology/topology-id";
        }
        description
            "A type for an absolute reference a topology instance.";
    }
    typedef node-leafref {
        type leafref {
            path "/network-topology/topology/node/node-id";
        }
        description

            "A type for an absolute reference to a node instance.";
    }
    typedef link-leafref {
        type leafref {
            path "/network-topology/topology/link/link-id";
        }
        description
            "A type for an absolute reference a link instance.";
    }
    
    typedef link-type {
        type enumeration {
            enum ge;
            enum 10ge-lan;
            enum 10ge-wan;
            enum 40ge;
            enum 100ge;
            enum otu1;
            enum otu2;
            enum otu2e;
            enum otu3;
            enum otu3e;
            enum otu4;
            enum odu0;
            enum odu1;
            enum odu2;
            enum odu2e;
            enum odu3;
            enum odu3e;
            enum odu4;  
            enum unknown; 
        }
    }
    typedef link-status-type {
        type enumeration {
            enum down;
            enum normal;
            enum unknown;
        }
    }

    grouping node-connector-attributes {

        leaf node-connector-id {
            type tport:node-connector-id;
        }
    }

    grouping node-attributes {

        leaf node-id {
            type tnode:node-id;            
        }
    }

    grouping link-attributes {
         leaf link-id {
            type ttypes:link-id;
        }
        container source {
            leaf source-node {
                mandatory true;
                type node-leafref;
                description
                    "Source node identifier, must be in same topology.";
            }
            leaf source-node-connector {
                type node-connector-leafref;
            }
        }
        container destination {
            leaf dest-node {
                mandatory true;
                type node-leafref;
                description
                    "Destination node identifier, must be in same topology.";
            }
            leaf dest-node-connector {
                type node-connector-leafref;               
            }
        }
    }
    grouping tunnel-attributes {
       leaf tunnel-id {
            type ttunnel:tunnel-id;
            description "The unique identifier for the global tunnel.";
        }
        leaf tunnel-type {
            type ttunnel:tunnel-type;
            description "The type of the tunnel.";
        }
    	leaf tunnel-operational-status {
            type ttunnel:tunnel-operational-status-type;
            description "The operational status of the tunnel.";
        }
		leaf deployment-status {
            type ttypes:deployment-status-type;
            description "The status of the deployment.";
        } 
             
        leaf active-path-status {
       		type ttypes:active-path-status-type;
            description "The status of the active path.";
    	}
		leaf-list service-ref {
            type ttypes:service-ref;
        }				
		leaf src-tunnel-ref {
        	type ttunnel:tunnel-ref;
    	}
    	leaf dest-tunnel-ref {
        	type ttunnel:tunnel-ref;
    	}
    	leaf working-path-status {
        	type ttunnel:tunnel-operational-status-type;
            description "The status of the working path.";
    	}
        leaf protection-path-status {
        	type ttunnel:tunnel-operational-status-type;
            description "The status of the protection path.";
    	}
    	
        list "working-path-xc" {
        	key "index";
        	leaf index {
	            type string;
	            description "index.";
	        }
   		 	leaf tunnel-xc-ref {
            	type ttunnelxc:tunnel-xc-ref;
            }
        } 
        list "protection-path-xc" {
        	key "index";
        	leaf index {
	            type string;
	            description "index.";
	        }
   		 	leaf tunnel-xc-ref {
            	type ttunnelxc:tunnel-xc-ref;
            }
        }   
    }


    container network-topology {
        list topology {
            key "topology-id";
	        leaf topology-id {
	            type ttypes:topology-id;
	            description "The unique identifier for the topology.";
	        }
	        leaf local-id {
	            type string;
	            description "The unique identifier in a particular local domain.";
	        } 
	        leaf network-type {
				type ttypes:network-type;
	  	    	description "The type of the network.";
	        } 
	        leaf provider {
	            type string;
	            description "The name of the network provider who operates the topology, TELCO.";
	        }
	        leaf lower-layer-path-computation-feature {
	            type ttypes:enabled-type;
	            description "The supporting feature of the lower layer path computation in the topology.";
	        }
	        leaf complete-path-set-provision-feature {
	            type ttypes:enabled-type;
	            description "The supporting feature of the complete path set provision in the topology.";
	        }
            list node {

                key "node-id";
                uses node-attributes;
                
                list node-connector {

                    key "node-connector-id";
                    uses node-connector-attributes;
                }
            }

            list link {

                key "link-id";
                uses link-attributes;

             }
        }
        list tunnel {
            key "tunnel-id";
            uses tunnel-attributes;
        }
    }
}
