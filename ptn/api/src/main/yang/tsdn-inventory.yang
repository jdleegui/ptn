module tsdn-inventory {
    yang-version 1;
    namespace "urn:opendaylight:params:xml:ns:yang:tsdn-inventory";
    prefix "tinv";
    
    import ietf-inet-types { prefix inet; revision-date "2013-07-15"; }
    import yang-ext { prefix ext; revision-date "2013-07-09"; }
    import tsdn-general-types { prefix ttypes; revision-date "2015-01-05"; }
    import tsdn-port { prefix tport; revision-date "2015-01-05"; }
    import tsdn-node { prefix tnode; revision-date "2015-01-05"; }
    import tsdn-tunnel { prefix "ttunnel"; revision-date "2015-01-05"; }
    import tsdn-tunnel-xc { prefix "ttunnelxc"; revision-date "2015-01-05"; }
    import tsdn-access-if { prefix "taccessif"; revision-date "2015-01-05"; }

    revision "2015-01-05" {
        description "Initial revision of tsdn inventory model";
    }

    grouping node-connector {

        leaf node-connector-id {
            type tport:node-connector-id;
            description "The unique identifier for the node-connector.";
        }
        uses tport:common-port;
        uses tport:physical-port;
    }

    grouping node {

        leaf node-id {
            type tnode:node-id;
            description "The unique identifier for the node.";
        }
    
        uses tnode:common-node;        
        list "node-connector" {
            key "node-connector-id";
            ext:context-instance tport:node-connector-context;            
            uses node-connector;
        }
        
        leaf topology-ref {
            type ttypes:topology-ref;
        }
    }
    
    container nodes {
        description "The root container of all nodes.";
        list node {
            key "node-id";
            ext:context-instance tnode:node-context;
            uses node; 
        }
    }
      
    notification node-updated {
        description "describes that something on the node has been updated";
        leaf node-ref {
            ext:context-reference tnode:node-context;
            type tnode:node-ref;
        }
        uses node;
    }
    notification node-removed {
    	description "describes that the node has been removed";
        leaf node-ref {
            ext:context-reference tnode:node-context;
            type tnode:node-ref;
        }
    }
	notification node-connector-updated {
		description "describes that something on the node-connector has been updated";
        leaf node-connector-ref {
            ext:context-reference tport:node-connector-context;
            type tport:node-connector-ref;
        }
        uses node-connector;
    }
    notification node-connector-removed {
    	description "describes that the node-connector has been removed";
        leaf node-connector-ref {
            ext:context-reference tport:node-connector-context;
            type tport:node-connector-ref;
        }
    }

    notification tunnel-updated {
		description "describes that something on the tunnel has been updated";
        leaf node-ref {
            ext:context-reference tnode:node-context;
            type tnode:node-ref;
        }
        leaf service-id {
            type ttypes:service-id;
            description "The unique identifier for the service.";
        }
    }
    notification tunnel-removed {
    	description "describes that the tunnel has been removed";
        leaf node-ref {
            ext:context-reference tnode:node-context;
            type tnode:node-ref;
        }
        leaf tunnel-id {
            type ttunnel:tunnel-id;
            description "The unique identifier for the tunnel.";
        }
    }
    notification tunnel-xc-updated {
		description "describes that something on the tunnel cross-connect has been updated";
        leaf node-ref {
            ext:context-reference tnode:node-context;
            type tnode:node-ref;
        }
        leaf service-id {
            type ttypes:service-id;
            description "The unique identifier for the service.";
        }
    }
    notification tunnel-xc-removed {
    	description "describes that the tunnel cross-connect has been removed";
        leaf node-ref {
            ext:context-reference tnode:node-context;
            type tnode:node-ref;
        }
        leaf tunnel-xc-id {
            type ttunnelxc:tunnel-xc-id;
            description "The unique identifier for the tunnel xc.";
        }
    }
    notification access-if-updated {
		description "describes that something on the access-if has been updated";
        leaf node-ref {
            ext:context-reference tnode:node-context;
            type tnode:node-ref;
        }
        leaf service-id {
            type ttypes:service-id;
            description "The unique identifier for the service.";
        }
    }
    notification access-if-removed {
    	description "describes that the access-if has been removed";
        leaf node-ref {
            ext:context-reference tnode:node-context;
            type tnode:node-ref;
        }
        leaf access-if-id {
            type taccessif:access-if-id;
            description "The unique identifier for the access-if-id.";
        }
    }
    notification delegated-service-updated {
		description "describes that something on the delegated-service has been updated";
        leaf node-ref {
            ext:context-reference tnode:node-context;
            type tnode:node-ref;
        }
        leaf service-id {
            type ttypes:service-id;
            description "The unique identifier for the service.";
        }
    }
    notification delegated-service-removed {
    	description "describes that the delegated-service has been removed";
        leaf node-ref {
            ext:context-reference tnode:node-context;
            type tnode:node-ref;
        }
        leaf service-id {
        	type ttypes:service-id;
            description "The unique identifier for the service.";
    	}
    }
    notification complete-path-set-provision-service-updated {
		description "describes that something on the complete-path-set-provision-service has been updated";
        leaf node-ref {
            ext:context-reference tnode:node-context;
            type tnode:node-ref;
        }
        leaf service-id {
            type ttypes:service-id;
            description "The unique identifier for the service.";
        }
    }
    notification complete-path-set-provision-service-removed {
    	description "describes that the complete-path-set-provision-service has been removed";
        leaf node-ref {
            ext:context-reference tnode:node-context;
            type tnode:node-ref;
        }
        leaf service-id {
        	type ttypes:service-id;
            description "The unique identifier for the service.";
    	}
    }
                
    rpc get-node {
    	description "get information of the node";
    	input {
    		leaf node-ref {
            	ext:context-reference tnode:node-context;
            	type tnode:node-ref;
        	}
    	    leaf node-id {
 	            type tnode:node-id;
           		description "The unique identifier for the node.";
    	    }
    	}
    	output {
	  	    leaf response {
	  	    	type ttypes:response-type;
	  	    	description "The type of the response.";
	  	   	}
		  	leaf reason {
	            type string;
	        }
	  	   	uses node;
    	}
    }
    rpc get-node-connector {
    	description "get information of the node-connector";
    	input {
    		leaf node-ref {
            	ext:context-reference tnode:node-context;
            	type tnode:node-ref;
        	}
    	    leaf node-connector-id {
 	            type tport:node-connector-id;
            	description "The unique identifier for the node-connector.";
    	    }
    	}
    	output {
	  	    leaf response {
	  	    	type ttypes:response-type;
	  	    	description "The type of the response.";
	  	   	}
		  	leaf reason {
	            type string;
	        }
	  	   	uses node-connector;
    	}
    }
    rpc set-tunnel {
    	description "set the tunnel";
    	input {
    		leaf node-ref {
            	ext:context-reference tnode:node-context;
            	type tnode:node-ref;
        	}
        	leaf service-id {
            	type ttypes:service-id;
            	description "The unique identifier for the service.";
        	}
    	}
    	output {
	  	    leaf response {
	  	    	type ttypes:response-type;
	  	    	description "The type of the response.";
	  	   	}
		  	leaf reason {
	            type string;
	        }
    	}
    } 
    rpc set-tunnel-xc {
    	description "set the tunnel cross-connect";
    	input {
    		leaf node-ref {
            	ext:context-reference tnode:node-context;
            	type tnode:node-ref;
        	}
        	leaf service-id {
            	type ttypes:service-id;
            	description "The unique identifier for the service.";
        	}
	   	}
    	output {
	  	    leaf response {
	  	    	type ttypes:response-type;
	  	    	description "The type of the response.";
	  	   	}
		  	leaf reason {
	            type string;
	        }
    	}
    } 
    rpc set-access-if {
    	description "set the access if";
    	input {
    		leaf node-ref {
            	ext:context-reference tnode:node-context;
            	type tnode:node-ref;
        	}
        	leaf service-id {
            	type ttypes:service-id;
            	description "The unique identifier for the service.";
        	}
    	}
    	output {
	  	    leaf response {
	  	    	type ttypes:response-type;
	  	    	description "The type of the response.";
	  	   	}
		  	leaf reason {
	            type string;
	        }
    	}
    } 
    rpc update-tunnel {
    	description "update the tunnel";
    	input {
    		leaf node-ref {
            	ext:context-reference tnode:node-context;
            	type tnode:node-ref;
        	}
        	leaf service-id {
            	type ttypes:service-id;
            	description "The unique identifier for the service.";
        	}
    	}
    	output {
	  	    leaf response {
	  	    	type ttypes:response-type;
	  	    	description "The type of the response.";
	  	   	}
		  	leaf reason {
	            type string;
	        }
    	}
    } 
    rpc update-tunnel-xc {
    	description "update the tunnel cross-connect";
    	input {
    		leaf node-ref {
            	ext:context-reference tnode:node-context;
            	type tnode:node-ref;
        	}
        	leaf service-id {
            	type ttypes:service-id;
            	description "The unique identifier for the service.";
        	}
	   	}
    	output {
	  	    leaf response {
	  	    	type ttypes:response-type;
	  	    	description "The type of the response.";
	  	   	}
		  	leaf reason {
	            type string;
	        }
    	}
    } 
    rpc update-access-if {
    	description "update the access if";
    	input {
    		leaf node-ref {
            	ext:context-reference tnode:node-context;
            	type tnode:node-ref;
        	}
        	leaf service-id {
            	type ttypes:service-id;
            	description "The unique identifier for the service.";
        	}
    	}
    	output {
	  	    leaf response {
	  	    	type ttypes:response-type;
	  	    	description "The type of the response.";
	  	   	}
		  	leaf reason {
	            type string;
	        }
    	}
    }
    rpc get-tunnel {
    	description "get information of the tunnel";
    	input {
    		leaf node-ref {
            	ext:context-reference tnode:node-context;
            	type tnode:node-ref;
        	}
    	    leaf tunnel-id {
 	           type ttunnel:tunnel-id;
            	description "The unique identifier for the tunnel.";
    	    }
    	}
    	output {
	  	    leaf response {
	  	    	type ttypes:response-type;
	  	    	description "The type of the response.";
	  	   	}
		  	leaf reason {
	            type string;
	        }
    	}
    } 
    rpc get-tunnel-xc {
    	description "get information of the tunnel cross-connect";
    	input {
    		leaf node-ref {
            	ext:context-reference tnode:node-context;
            	type tnode:node-ref;
        	}
    	    leaf tunnel-xc-id {
 	            type ttunnelxc:tunnel-xc-id;
            	description "The unique identifier for the tunnel cross-connect.";
    	    }
    	}
    	output {
	  	    leaf response {
	  	    	type ttypes:response-type;
	  	    	description "The type of the response.";
	  	   	}
		  	leaf reason {
	            type string;
	        }
    	}
    } 
    rpc get-access-if {
    	description "get information of the access if";
    	input {
    		leaf node-ref {
            	ext:context-reference tnode:node-context;
            	type tnode:node-ref;
        	}
    	    leaf access-if-id {
 	            type taccessif:access-if-id;
            	description "The unique identifier for the access-if.";
    	    }
    	}
    	output {
	  	    leaf response {
	  	    	type ttypes:response-type;
	  	    	description "The type of the response.";
	  	   	}
		  	leaf reason {
	            type string;
	        }
    	}
    }
    rpc delete-tunnel {
    	description "delete the tunnel";
    	input {
    		leaf node-ref {
            	ext:context-reference tnode:node-context;
            	type tnode:node-ref;
        	}
    	    leaf tunnel-id {
 	            type ttunnel:tunnel-id;
           		description "The unique identifier for the tunnel.";
    	    }
    	}
    	output {
	  	    leaf response {
	  	    	type ttypes:response-type;
	  	    	description "The type of the response.";
	  	   	}
		  	leaf reason {
	            type string;
	        }
    	}
    } 
    rpc delete-tunnel-xc {
    	description "delete the tunnel cross-connect";
    	input {
    		leaf node-ref {
            	ext:context-reference tnode:node-context;
            	type tnode:node-ref;
        	}
    	    leaf tunnel-xc-id {
 	            type ttunnelxc:tunnel-xc-id;
           		description "The unique identifier for the tunnel cross-connect.";
    	    }
    	}
    	output {
	  	    leaf response {
	  	    	type ttypes:response-type;
	  	    	description "The type of the response.";
	  	   	}
		  	leaf reason {
	            type string;
	        }
    	}
    } 
    rpc delete-access-if {
    	description "delete the access if";
    	input {
    		leaf node-ref {
            	ext:context-reference tnode:node-context;
            	type tnode:node-ref;
        	}
    	    leaf access-if-id {
 	            type taccessif:access-if-id;
           		description "The unique identifier for the access if.";
    	    }
    	}
    	output {
	  	    leaf response {
	  	    	type ttypes:response-type;
	  	    	description "The type of the response.";
	  	   	}
		  	leaf reason {
	            type string;
	        }
    	}
    }
    rpc set-delegated-service {
    	description "set the delegated service";
    	input {
    		leaf domain-node-ref {
            	ext:context-reference tnode:node-context;
            	type tnode:node-ref;
        	}
        	leaf service-id {
            	type ttypes:service-id;
           		description "The unique identifier for the service.";
        	}
    	}
    	output {
	  	    leaf response {
	  	    	type ttypes:response-type;
	  	    	description "The type of the response.";
	  	   	}
		  	leaf reason {
	            type string;
	        }
    	}
    }
    rpc update-delegated-service {
    	description "update the delegated service";
    	input {
    		leaf domain-node-ref {
            	ext:context-reference tnode:node-context;
            	type tnode:node-ref;
        	}
        	leaf service-id {
            	type ttypes:service-id;
           		description "The unique identifier for the service.";
        	}
    	}
    	output {
	  	    leaf response {
	  	    	type ttypes:response-type;
	  	    	description "The type of the response.";
	  	   	}
		  	leaf reason {
	            type string;
	        }
    	}
    }
    rpc get-delegated-service {
    	description "get information of the delegated service";
    	input {
    		leaf domain-node-ref {
            	ext:context-reference tnode:node-context;
            	type tnode:node-ref;
        	}
        	leaf service-id {
            	type ttypes:service-id;
           		description "The unique identifier for the service.";
        	}
    	}
    	output {
	  	    leaf response {
	  	    	type ttypes:response-type;
	  	    	description "The type of the response.";
	  	   	}
		  	leaf reason {
	            type string;
	        }
    	}
    }
    rpc delete-delegated-service {
    	description "delete the delegated service";
    	input {
    		leaf domain-node-ref {
            	ext:context-reference tnode:node-context;
            	type tnode:node-ref;
        	}
        	leaf service-id {
            	type ttypes:service-id;
           		description "The unique identifier for the service.";
        	}
    	}
    	output {
	  	    leaf response {
	  	    	type ttypes:response-type;
	  	    	description "The type of the response.";
	  	   	}
		  	leaf reason {
	            type string;
	        }
    	}
    } 
    rpc set-complete-path-set-provision-service {
    	description "set the complete path set provision service";
    	input {
    		leaf domain-node-ref {
            	ext:context-reference tnode:node-context;
            	type tnode:node-ref;
        	}
        	leaf service-id {
            	type ttypes:service-id;
           		description "The unique identifier for the service.";
        	}
    	}
    	output {
	  	    leaf response {
	  	    	type ttypes:response-type;
	  	    	description "The type of the response.";
	  	   	}
		  	leaf reason {
	            type string;
	        }
    	}
    }
    rpc update-complete-path-set-provision-service {
    	description "update the complete path set provision service";
    	input {
    		leaf domain-node-ref {
            	ext:context-reference tnode:node-context;
            	type tnode:node-ref;
        	}
        	leaf service-id {
            	type ttypes:service-id;
           		description "The unique identifier for the service.";
        	}
    	}
    	output {
	  	    leaf response {
	  	    	type ttypes:response-type;
	  	    	description "The type of the response.";
	  	   	}
		  	leaf reason {
	            type string;
	        }
    	}
    }
    rpc get-complete-path-set-provision-service {
    	description "get information of the complete path set provision service";
    	input {
    		leaf domain-node-ref {
            	ext:context-reference tnode:node-context;
            	type tnode:node-ref;
        	}
        	leaf service-id {
            	type ttypes:service-id;
           		description "The unique identifier for the service.";
        	}
    	}
    	output {
	  	    leaf response {
	  	    	type ttypes:response-type;
	  	    	description "The type of the response.";
	  	   	}
		  	leaf reason {
	            type string;
	        }
    	}
    }
    rpc delete-complete-path-set-provision-service {
    	description "delete the complete path set provision service";
    	input {
    		leaf domain-node-ref {
            	ext:context-reference tnode:node-context;
            	type tnode:node-ref;
        	}
        	leaf service-id {
            	type ttypes:service-id;
           		description "The unique identifier for the service.";
        	}
    	}
    	output {
	  	    leaf response {
	  	    	type ttypes:response-type;
	  	    	description "The type of the response.";
	  	   	}
		  	leaf reason {
	            type string;
	        }
    	}
    }
}
