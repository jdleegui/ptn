module mpls-tp-topology-discovery  {
    yang-version 1;
    namespace "urn:opendaylight:params:xml:ns:yang:mpls-tp-topology-discovery";
    prefix "mttd";

    import ietf-inet-types {prefix inet; revision-date "2013-07-15";}
    import yang-ext {prefix ext; revision-date "2013-07-09";}
 	import tsdn-topology-discovery {prefix "ttd"; revision-date "2015-01-05"; }
    import mpls-tp-topology-inventory {prefix "mttinv"; revision-date "2015-01-05"; }

    revision 2015-01-05 {
        description
            "Initial revision.";
    }

    augment "/ttd:link-updated" {
        ext:augment-identifier "mpls-tp-link-updated";
		uses mttinv:mpls-tp-link;
    }
}
