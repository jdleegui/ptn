module tsdn-tunnel {
    yang-version 1;
    namespace "urn:opendaylight:params:xml:ns:yang:tsdn-tunnel";
    prefix "ttunnel";
    
    import ietf-inet-types {prefix inet; revision-date "2013-07-15";}
//   import yang-ext {prefix ext; revision-date "2013-07-09";}
    import tsdn-general-types {prefix "ttypes"; revision-date "2015-01-05"; }
 
 
    revision "2015-01-05" {
        description "Initial revision of tunnel model";
    }

    typedef tunnel-id {
        //type inet:uri; 
        type string;  
        description "Identifier for a particular tunnel";
    }
    typedef tunnel-ref {
        type instance-identifier;
        description "A reference that points to an nodes/node/{node_id}/tunnel in the data tree.";
    }

    typedef tunnel-operational-status-type {
        type enumeration {
            enum normal;
            enum unknown;
            enum broken;
            enum creating;
            enum updating;
            enum deleting;
            enum interrupted;             
        }        
    }
    typedef tunnel-configuration-action-type {
        type enumeration {
            enum unknown;
            enum create;
            enum update;
            enum delete;
            enum interrupt;  
        }        
    }

    typedef tunnel-stage-type {
        type enumeration {
            enum 0;
            enum 1;
            enum 2;
            enum 3;
        }
    }
 
    typedef tunnel-type {
        type enumeration {
            enum packet;
            enum otn;  
            enum sdh;
            enum wdm;
            enum all;   
            enum unknown;      
        }
    }
    
    grouping common-tunnel {
    	leaf local-id {
            type string;
            description "The unique identifier in a particular local domain.";
        }
        leaf name {
            type string;
            description "The name of the instance.";
        }
        leaf tunnel-type {
            type tunnel-type;
            description "The type of the tunnel.";
        }
    	leaf tunnel-operational-status {
            type tunnel-operational-status-type;
            description "The operational status of the tunnel.";
        }
        leaf tunnel-configuration-action {
            type tunnel-configuration-action-type;
            description "The last configuration action of the tunnel.";
        }
        leaf tunnel-configuration-result {
            type ttypes:configuration-result-type;
            description "The configuration result of the action.";
        }

        leaf deployment-enabler {
            type ttypes:enabler-type;
            description "The enabler of the deployment.";
        } 
		leaf deployment-status {
            type ttypes:deployment-status-type;
            description "The status of the deployment.";
        }  
    }
}
