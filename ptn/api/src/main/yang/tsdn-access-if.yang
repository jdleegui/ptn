module tsdn-access-if {
    yang-version 1;
    namespace "urn:opendaylight:params:xml:ns:yang:tsdn-access-if";
    prefix "tport";
    
   import ietf-inet-types {prefix inet; revision-date "2013-07-15";}
//   import yang-ext {prefix ext; revision-date "2013-07-09";}
     import tsdn-general-types {prefix ttypes; revision-date "2015-01-05";} 
 
 
    revision "2015-01-05" {
        description "Initial revision of access-if model";
    }

    typedef access-if-id {
        //type inet:uri; 
        type string;  
        description "Identifier for a particular access-if";
    }
    
    typedef access-if-ref {
        type instance-identifier;
        description "A reference that points to an services/service in the data tree.";
    }

    typedef access-if-operational-status-type {
        type enumeration {
            enum normal;
            enum unknown;
            enum broken;
            enum creating;
            enum updating;
            enum deleting;
            enum interrupted;           
        }        
    }
    typedef access-if-configuration-action-type {
        type enumeration {
            enum unknown;
            enum create;
            enum update;
            enum delete;
            enum interrupt;   
        }        
    }
 
    typedef access-if-type {
        type enumeration {
            enum ge;
            enum 10ge-lan;
            enum 10ge-wan;
            enum fe;
            enum ge-gfpt;
            enum ge-ttt-agmp;
            enum 40ge;
            enum 100ge;
            enum otu1;
            enum otu2;
            enum otu2e;
            enum otu3;
            enum otu3e;
            enum otu4;
            enum odu0;
            enum odu1;
            enum odu2;
            enum odu2e;
            enum odu3;
            enum odu3e;
            enum odu4;  
            enum odu-flex;
            enum stm1;
            enum stm4;
            enum stm16;
            enum stm64;
            enum stm256;
            enum oc3;                
            enum oc12;
            enum oc48;
            enum oc192;
            enum oc768;
            enum wdm;
            enum all; 
            enum unknown;        
        }
    }

    
    grouping common-access-if {
    	leaf local-id {
            type string;
            description "The unique identifier in a particular local domain.";
        }        
        leaf name {
            type string;
            description "The name of the instance.";
        }
        leaf access-if-type {
            type access-if-type;
	  	    description "The type of the access if.";
        }
        leaf access-if-operational-status {
            type access-if-operational-status-type;
            description "The operational status of the access if.";
        }
        leaf access-if-configuration-action {
            type access-if-configuration-action-type;
            description "The last configuration action of the access if.";
        }
        leaf access-if-configuration-result {
            type ttypes:configuration-result-type;
            description "The configuration result of the action.";
        }
        leaf deployment-enabler {
            type ttypes:enabler-type;
            description "The enabler of the deployment.";
        } 
		leaf deployment-status {
            type ttypes:deployment-status-type;
            description "The status of the deployment.";
        } 
    }
}
