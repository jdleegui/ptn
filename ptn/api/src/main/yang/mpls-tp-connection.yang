module mpls-tp-connection {
    yang-version 1;
    namespace "urn:opendaylight:params:xml:ns:yang:mpls-tp-connection";
    prefix "mtcon";
    
   import ietf-inet-types {prefix inet; revision-date "2013-07-15";}
   import yang-ext {prefix ext; revision-date "2013-07-09";}
   import tsdn-connection {prefix tcon; revision-date "2015-01-05";} 
   import tsdn-port {prefix "tport"; revision-date "2015-01-05"; }
   import tsdn-node {prefix "tnode"; revision-date "2015-01-05"; }
   import tsdn-general-types {prefix "ttypes"; revision-date "2015-01-05"; }
   import tsdn-access-if {prefix "taccessif"; revision-date "2015-01-05"; }
   import tsdn-tunnel {prefix "ttunnel"; revision-date "2015-01-05"; }
   import tsdn-tunnel-xc {prefix "ttunnelxc"; revision-date "2015-01-05"; }
   import mpls-tp-general-types {prefix "mttypes"; revision-date "2015-01-05"; }

    revision "2015-01-05" {
        description "Initial revision of mpls-tp connection";
    }

	 grouping connection-info {
        leaf info-ref {
			type union {
				type taccessif:access-if-ref;
				type ttunnel:tunnel-ref;
				type ttunnelxc:tunnel-xc-ref;
				type ttypes:link-ref;
				type mttypes:pw-ref;
				type mttypes:pw-xc-ref;
				type mttypes:mpls-if-ref;
			}
        }
        leaf termination-point-type {
    		type tport:port-type;
    		description "The type of the termination point.";
        }
        leaf service-rate {
      		type uint32;
	   	}
	 }
	 

     grouping mpls-tp-connection {

		leaf node-ref {
            type tnode:node-ref;
        }        
        leaf connection-type {
            type tcon:connection-type;
    		description "The type of the connection.";
        }        
        list ingress-info {
        	key "ingress-id";
        	leaf ingress-id {
        		type string;
            	//type inet:uri;   
        	}
        	uses connection-info;
        }
        list egress-info {
        	key "egress-id";
        	leaf egress-id {
            	//type inet:uri; 
            	type string;  
        	}
        	uses connection-info;
        }

        leaf next-connection-index {
            type tcon:connection-id;
        }
    }
    
    grouping nni-connection-info {
        leaf tunnel-ref {
			type ttunnel:tunnel-ref;
		}
		leaf mpls-if-ref {
			type mttypes:mpls-if-ref;
		}
		leaf node-connector-ref {
			type tport:node-connector-ref;
		}
		uses mttypes:label-set;	
	 }
	 

     grouping mpls-tp-nni-connection {

		leaf node-ref {
            type tnode:node-ref;
        }        
        container ingress-interface {
        	uses nni-connection-info;
        }
        container egress-interface {
        	uses nni-connection-info;
        }
        leaf next-connection-index {
            type tcon:connection-id;
        }
    }
}
