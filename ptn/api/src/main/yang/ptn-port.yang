module ptn-port {
    yang-version 1;
    namespace "urn:opendaylight:params:xml:ns:yang:ptn-port";
    prefix "ptnport";
    
   import ietf-inet-types {prefix inet; revision-date "2013-07-15";}
   import yang-ext {prefix ext; revision-date "2013-07-09";}
   import tsdn-inventory {prefix "inv"; revision-date "2015-01-05"; }
   
    revision "2015-01-05" {
        description "Initial revision of ptn port model";
    }

    grouping supported-bandwidth {
        leaf maximum-bandwidth {
            type uint32;
        }
        leaf available-bandwidth {
            type uint32;
        }        
    }
    grouping ip-address {
        leaf local {
            type inet:ip-address;
        }
        leaf remote {
            type inet:ip-address;
        }
    }
    

}
