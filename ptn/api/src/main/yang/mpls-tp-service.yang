module mpls-tp-service {
    yang-version 1;
    namespace "urn:opendaylight:params:xml:ns:yang:mpls-tp-service";
    prefix "mtser";
    
   import ietf-inet-types {prefix inet; revision-date "2013-07-15";}
   import yang-ext {prefix ext; revision-date "2013-07-09";}
   import tsdn-inventory {prefix "inv"; revision-date "2015-01-05"; }
   import mpls-tp-inventory {prefix "mtinv"; revision-date "2015-01-05"; }
   import tsdn-service {prefix "ser"; revision-date "2015-01-05"; }
   import tsdn-node {prefix "tnode"; revision-date "2015-01-05"; }
   import tsdn-port {prefix "tport"; revision-date "2015-01-05"; } 
   import tsdn-access-if {prefix "taccessif"; revision-date "2015-01-05"; } 
   import tsdn-general-types {prefix "ttypes"; revision-date "2015-01-05"; }   
   import tsdn-connection {prefix tcon; revision-date "2015-01-05";} 
   import mpls-tp-connection {prefix mtcon; revision-date "2015-01-05";} 
   import mpls-tp-general-types {prefix "mttypes"; revision-date "2015-01-05"; }   
   import mpls-tp-provision {prefix "mtprov"; revision-date "2015-01-05"; }
 

    revision "2015-01-05" {
        description "Initial revision of mpls-tp service model";
    }
    

	grouping oper-path-connection {
        leaf start-connection-index{
	        type tcon:connection-id;
	    }    
	    list connection{
	    	key "index";
	    	leaf index {
	       		type tcon:connection-id;
	        }
			uses mtcon:mpls-tp-connection;           
	    }
	}
	grouping path-connection {
        leaf start-connection-index{
	        type tcon:connection-id;
	    }    
	    list connection{
	    	key "index";
	    	leaf index {
	       		type tcon:connection-id;
	        }
			uses mtcon:mpls-tp-nni-connection;           
	    }
	}
    
    grouping access-if-attribute {
    
        leaf node-connector-ref {
            type tport:node-connector-ref;
        }
        leaf access-if-type {
            type taccessif:access-if-type;
	  	    description "The type of the access if.";
        }
        list port-constraint{
            key "index";
         
            leaf index {
	            type ttypes:constraint-id;
        	}
            uses ttypes:common-constraint;
            leaf port-constraint-type {
            	type ttypes:port-constraint-type;
	  		    description "The type of the port constraint.";
        	}			
        }
    }
   
    grouping mpls-tp-service {
        
        leaf active-path-status {
            type ttypes:active-path-status-type;
            description "The status of the active path.";
        }
        leaf-list tunnel-id {
            type string;
            description "The unique identifier for the global tunnel.";
        }
        leaf-list pw-id {
            type string;
            description "The unique identifier for the global pw.";
        }
        leaf vpn-id {
      		type uint16;
      		description "The unique identifier for the vpn-id.";
	   	}
       
        uses mttypes:mpls-tp-flow-qos;
       
		list service-constraint{
            key "index";
            leaf index {
	            type ttypes:constraint-id;
        	}
            uses ttypes:common-constraint;
            leaf service-constraint-type {
            	type ttypes:service-constraint-type;
	  		    description "The type of the service constraint.";
        	}
        }
        list node {
        	key "node-id";
        	leaf node-id {
	            type tnode:node-id;
	            description "The unique identifier for the node.";
	        }
		    leaf node-ref {
	            type tnode:node-ref;
	        }
	        leaf node-role {
	        	type tnode:node-role-type;
	  		    description "The type of the node role.";
	        }  
	        list access-if {
	            key "index";	
			    leaf index {
		            type string;
		            description "index.";
		        }			
	            uses access-if-attribute;	
	        }
        }

        list path {
        	key "index";
        	leaf index {
	            type string;
	            description "index.";
	        }
			leaf path-type {
	            type ttypes:path-type;
	    		description "The type of the path.";
	        } 
			uses path-connection;

	    }
	
        list oper-pw-connection {
        	key "pw-id";
        	leaf pw-id {
	            type mttypes:pw-id;
	            description "The unique identifier for the pw.";
	        }
	        leaf pw-ref {
	        	type mttypes:pw-ref;
	        }	
			container working-path	{
				uses oper-path-connection;
			}	
			container protection-path	{
				uses oper-path-connection;
			}     
	    }
               
        list pw-connection {
        	key "pw-id";
        	leaf pw-id {
	            type string;
	            description "The unique identifier for the pw.";
	        }
			container working-path	{
				uses mtprov:path-connection;
			}	
			container protection-path	{
				uses mtprov:path-connection;
			}     
	    }

    }
 

    augment "/ser:services/ser:service" {
        ext:augment-identifier "mpls-tp-capable-service";
        uses mpls-tp-service;
    }
     
    augment "/ser:set-service/ser:input" {
        ext:augment-identifier "mpls-tp-set-service-input";
		uses mpls-tp-service;
    }
    augment "/ser:update-service/ser:input" {
        ext:augment-identifier "mpls-tp-update-service-input";
		uses mpls-tp-service;
    }
    augment "/ser:get-service/ser:output" {
        ext:augment-identifier "mpls-tp-get-service-output";
		uses mpls-tp-service;
    }    
       
    augment "/ser:service-updated" {
        ext:augment-identifier "mpls-tp-service-updated";
		uses mpls-tp-service;
    }


}
