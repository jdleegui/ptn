module tsdn-general-types {
    yang-version 1;
    namespace "urn:opendaylight:params:xml:ns:yang:tsdn-general-types";
    prefix "ttypes";
    
   import ietf-inet-types {prefix inet; revision-date "2013-07-15";}
   import yang-ext {prefix ext; revision-date "2013-07-09";}


    revision "2015-01-05" {
        description "Initial revision of tsdn general types";
    }

    typedef service-id {
        //type inet:uri; 
        type string;  
        description "Identifier for a particular service";
    }
    typedef constraint-id {
        //type inet:uri; 
        type string;  
        description "Identifier for a particular constraint";
    }    
     
    identity service-context {
        description "A node-context is a classifier for node elements which allows an RPC to provide a service on behalf of a particular element in the data tree.";
    }  

    typedef service-ref {
        type instance-identifier;
        description "A reference that points to an services/service in the data tree.";
    }
    typedef link-id {
        //type inet:uri; 
        type string;  
        description "Identifier for a particular link";
    }
    
    typedef link-ref {
        type instance-identifier;
        description "A reference that points to an nodes/node in the data tree.";
    }
    
    typedef topology-id {
        //type inet:uri; 
        type string;  
        description "Identifier for a particular topology";
    }
    typedef topology-ref {
        type instance-identifier;
        description "A reference that points to an network-topology/topology in the data tree.";
    }
/*    typedef topology-type {
        type enumeration {
            enum otn;
            enum sdh;
            enum ptn;
            enum mpls-tp;
            enum wdm;
            enum all;
            enum unknown;
        }
    }*/
    typedef service-direction-type {
        type enumeration {
            enum unidirection;
            enum bidirection;
            enum others;
            enum unknown;
        }
    } 
    typedef sla-type {
        type enumeration {
            enum gold;
            enum silver;
            enum bronze;
            enum best-effort;
            enum unknown;
        }
    } 
    typedef service-type {
        type enumeration {
            enum ptp;
            enum mptmp;
            enum ptmp;
            enum tunnel;
            enum unknown;
        }
    }
    typedef network-type {
        type enumeration {
            enum otn;
            enum sdh;
            enum ptn;
            enum mpls-tp;
            enum wdm;
            enum all;
            enum unknown;
        }
    }    

    typedef service-operational-status-type {
        type enumeration {
            enum normal;
            enum unknown;
            enum broken;
            enum creating;
            enum updating;
            enum deleting;
            enum interrupted;    
        }
    }
    typedef service-configuration-action-type {
        type enumeration {
            enum unknown;
            enum create;
            enum update;
            enum delete;
            enum interrupt;  
        }        
    }
    typedef active-path-status-type {
        type enumeration {
            enum unknown;
            enum broken;
            enum working-path-active;
            enum protection-path-active;
        }
    }
        
    typedef enabler-type {
        type enumeration {
            enum enable;
            enum disable;
            enum unknown;
        }
    }
    typedef enabled-type {
        type enumeration {
            enum enabled;
            enum disabled;
            enum unknown;
        }
    }
    typedef path-computation-priority-type {
        type enumeration {
            enum higher-layer-first;
            enum lower-layer-first;
            enum unknown;
        }
    }
    typedef deployment-status-type {
        type enumeration {
            enum not-reserved;
            enum reserved;
            enum applied;
            enum unknown;
        }
    }        
    typedef response-type {
        type enumeration {
            enum ok;
            enum not-ok;
            enum node-not-found;
            enum node-connector-not-found;
            enum unknown;
        }
    }
    typedef configuration-result-type {
        type enumeration {
            enum unknown;
            enum success;
            enum failure;
            enum interrupted;            
        }        
    }
   
    typedef signal-type {
        type enumeration {
            enum ge;
            enum 10ge-lan;
            enum 10ge-wan;
            enum ge-gfpt;
            enum ge-ttt-agmp;
            enum 40ge;
            enum 100ge;
            enum otu1;
            enum otu2;
            enum otu2e;
            enum otu3;
            enum otu3e;
            enum otu4;
            enum odu0;
            enum odu1;
            enum odu2;
            enum odu3;
            enum odu4;  
            enum odu-flex;
            enum stm1;
            enum stm4;
            enum stm16;
            enum stm64;
            enum stm256;
            enum oc3;                
            enum oc12;
            enum oc48;
            enum oc192;
            enum oc768;
            enum wdm;
            enum all; 
            enum unknown;         
        }
    }
    
   typedef tunnel-protection-type {
        type enumeration {
            enum tunnel-protection-no-protection;
            enum tunnel-protection-re-routing;
            enum tunnel-protection-one-for-one;
            enum tunnel-protection-one-plus-one;
            enum tunnel-protection-permanent-one-plus-one;
            enum tunnel-protection-re-routing-one-plus-one;
            enum tunnel-protection-unknown;
        }
    }
    typedef pw-protection-type {
        type enumeration {
            enum pw-protection-no-protection;
            enum pw-protection-re-routing;
            enum pw-protection-one-for-one;
            enum pw-protection-one-plus-one;
            enum pw-protection-permanent-one-plus-one;
            enum pw-protection-re-routing-one-plus-one;
            enum pw-protection-unknown;
        }
    } 
    typedef tunnel-protection-protocol-type {
        type enumeration {
            enum tunnel-protection-protocol-itu-t;
            enum tunnel-protection-protocol-ietf;
            enum tunnel-protection-protocol-unknown;
        }
    } 
    typedef pw-protection-protocol-type {
        type enumeration {
            enum pw-protection-protocol-itu-t;
            enum pw-protection-protocol-ietf;
            enum pw-protection-protocol-unknown;
        }
    } 
    typedef tunnel-protection-revert-type {
        type enumeration {
            enum tunnel-protection-revert-non-revertive;//default
            enum tunnel-protection-revert-revertive;
            enum tunnel-protection-revert-unknown;
        }
    }
    typedef pw-protection-revert-type {
        type enumeration {
            enum pw-protection-revert-non-revertive;//default
            enum pw-protection-revert-revertive;
            enum pw-protection-revert-unknown;
        }
    }
    typedef tunnel-oam-type {
        type enumeration {
        	enum tunnel-oam-no-oam;
            enum tunnel-oam-itu-t;
            enum tunnel-oam-ietf;
            enum tunnel-oam-unknown;
        }
    }
    typedef pw-oam-type {
        type enumeration {
            enum pw-oam-no-oam;
            enum pw-oam-itu-t;
            enum pw-oam-ietf;
            enum pw-oam-unknown;
        }
    }
    typedef tunnel-protection-hold-off-time {
        type enumeration {
            enum tunnel-protection-hold-off-time-default;//0 ms
            enum tunnel-protection-hold-off-time-value-set;
            enum tunnel-protection-hold-off-unknown;
        }
    }
    typedef pw-protection-hold-off-time {
        type enumeration {
            enum pw-protection-hold-off-time-default;//1000 ms
            enum pw-protection-hold-off-time-value-set;
            enum pw-protection-hold-off-unknown;
        }
    } 
    typedef tunnel-oam-message-interval-time {
        type enumeration {
            enum tunnel-oam-message-interval-time-default;//3.3 ms
            enum tunnel-oam-message-interval-time-value-set;
            enum tunnel-oam-message-interval-time-unknown;
        }
    }
    typedef pw-oam-message-interval-time {
        type enumeration {
            enum pw-oam-message-interval-time-default;//1000 ms
            enum pw-oam-message-interval-time-value-set;
            enum pw-oam-message-interval-time-unknown;
        }
    } 
    typedef path-type {
        type enumeration {
            enum working-path;
            enum protection-path;
            enum unknown;
        }
    } 
    typedef path-computation-constraint-type {
        type enumeration {
            enum include-node;
            enum exclude-node;
            enum include-pw-xc-node;
            enum include-tunnel;
            enum unknown;
        }
    }   
    
    typedef port-constraint-type {
        type enumeration {
            enum port-constraint-inner-vid;
            enum port-constraint-outer-vid;
            enum port-constraint-untagged;
            enum port-constraint-port-based;
        }
    }
    typedef service-constraint-type {
    	type enumeration {
       		enum tunnel-protection-revert-type;
			enum tunnel-protection-protocol-type;
			enum tunnel-protection-type;
			enum tunnel-protection-hold-off-time;
			enum tunnel-oam-message-interval-time;
			enum tunnel-oam-type;
			enum pw-protection-revert-type;
			enum pw-protection-protocol-type;
			enum pw-protection-type;
			enum pw-protection-hold-off-time;
			enum pw-oam-message-interval-time;
			enum pw-oam-type;
			enum path-computation-constraint-type;
		}
    }
    
    grouping common-constraint {
    	leaf name {
            type string;
            description "The name of the instance.";
        }

        leaf value {
   			type string;
        }
        leaf operator {
   			type string;
        }
    }
    
    grouping switching-capacity {
        leaf maximum-switching-bandwidth {
            type uint32;
        }
        leaf available-switching-bandwidth {
            type uint32;
        }
    }

}
