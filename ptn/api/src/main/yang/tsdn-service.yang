module tsdn-service {
    yang-version 1;
    namespace "urn:opendaylight:params:xml:ns:yang:tsdn-service";
    prefix "tser";
    
   import ietf-inet-types {prefix inet; revision-date "2013-07-15";}
   import yang-ext {prefix ext; revision-date "2013-07-09";}
   import tsdn-inventory {prefix "inv"; revision-date "2015-01-05"; }
   import tsdn-port {prefix "tport"; revision-date "2015-01-05"; }
   import tsdn-node {prefix "tnode"; revision-date "2015-01-05"; }
   import tsdn-general-types {prefix ttypes; revision-date "2015-01-05";} 
  

    revision "2015-01-05" {
        description "Initial revision of tsdn service model";
    }

    grouping service {
		leaf service-id {
	        type ttypes:service-id;
	        description "The unique identifier for the service.";
       	}
       	leaf service-name {
            type string;
            description "The name of the instance.";
        } 
       	leaf service-description {
            type string;
        }
        leaf service-local-id {
            type string;
            description "The unique identifier in a particular local domain.";
        }
       	leaf service-type {
            type ttypes:service-type;
	  	    description "The type of the service.";
        }
        leaf network-type {
            type ttypes:network-type;
	  	    description "The type of the network.";
        }
        leaf service-operational-status {
            type ttypes:service-operational-status-type;
            description "The operational status of the service.";
        }
        leaf service-configuration-action {
            type ttypes:service-configuration-action-type;
            description "The last configuration action of the service.";
        }
        leaf service-configuration-result {
            type ttypes:configuration-result-type;
            description "The configuration result of the action.";
        }
        leaf deployment-enabler {
            type ttypes:enabler-type;
            description "The enabler of the deployment.";
        } 
        leaf service-creation-date {
            type string;
        }
        leaf service-modification-date {
            type string;
        }
    }
    grouping service-attributes {

        leaf higher-layer-path-computation-feature {
            type ttypes:enabled-type;
            description "The supporting feature of the higher layer path computation.";
        }
        leaf path-computation-priority {
            type ttypes:path-computation-priority-type;
            description "The priority of the path computation.";
        }
    }
    
    container services {

        description "The root container of all services.";
		
	    
        list service {
            key "service-id";
            uses service;
        }
        uses service-attributes;
    }
    
    notification service-updated {

        leaf service-ref {
            type ttypes:service-ref;
        }
        uses service;
    }
    notification service-removed {

        leaf service-ref {
            type ttypes:service-ref;
        }
    }
    rpc set-service {
    	input {
			uses service;	
    	}
    	output {
	  	    leaf response {
	  	    	type ttypes:response-type;
	  		    description "The type of the response.";
	  	   	}
		  	leaf reason {
	            type string;
	        }
    	}
    }
    rpc update-service {
    	input {
			uses service;	
    	}
    	output {
	  	    leaf response {
	  	    	type ttypes:response-type;
	  		    description "The type of the response.";
	  	   	}
	  	   	leaf reason {
	            type string;
	        }
    	}
    }
    rpc get-service {
    	input {
    	    leaf service-id {
 	           type ttypes:service-id;
    	    }
    	}
    	output {
	  	    leaf response {
	  	    	type ttypes:response-type;
	  		    description "The type of the response.";
	  	   	}
		  	leaf reason {
	            type string;
	        }	  	   	
	  	   	uses service;
    	}
    }     
    rpc delete-service {
    	input {
    	    leaf service-id {
 	           type ttypes:service-id;
    	    }
    	}
    	output {
	  	    leaf response {
	  	    	type ttypes:response-type;
	  		    description "The type of the response.";
	  	   	}
		  	leaf reason {
	            type string;
	        }	  	   	
    	}
    } 
}
