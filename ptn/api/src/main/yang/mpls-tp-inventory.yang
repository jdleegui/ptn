module mpls-tp-inventory {
    yang-version 1;
    namespace "urn:opendaylight:params:xml:ns:yang:mpls-tp-inventory";
    prefix "mtinv";
    
//   import ietf-inet-types {prefix inet; revision-date "2013-07-15";}
   import yang-ext {prefix ext; revision-date "2013-07-09";}
   import tsdn-inventory {prefix "tinv"; revision-date "2015-01-05"; }
   import tsdn-tunnel {prefix "ttunnel"; revision-date "2015-01-05"; }
   import tsdn-tunnel-xc {prefix "ttunnelxc"; revision-date "2015-01-05"; }
   import tsdn-access-if {prefix "taccessif"; revision-date "2015-01-05"; }
   import ptn-port {prefix "pport"; revision-date "2015-01-05"; }
   import tsdn-general-types {prefix ttypes; revision-date "2015-01-05";} 
   import mpls-tp-general-types {prefix mttypes; revision-date "2015-01-05";}
   import tsdn-port {prefix "tport"; revision-date "2015-01-05"; } 
   import tsdn-node {prefix "tnode"; revision-date "2015-01-05"; } 
   import mpls-tp-provision {prefix "mtprov"; revision-date "2015-01-05"; } 

    revision "2015-01-05" {
        description "Initial revision of mpls-tp inventory model";
    }
    
/*    typedef node-leafref {
        type leafref {
            path "/tinv:nodes/tinv:node/tinv:node-id";
        }
    }
   
    typedef node-connector-leafref {
        type leafref {
            path "/tinv:nodes/tinv:node/tinv:node-connector/tinv:node-connector-id";
        }
    }
            
    typedef tunnel-leafref {
        type leafref {
            path "/tinv:nodes/tinv:node/tunnel/tunnel-id";
        }
    }
    
    typedef access-if-leafref {
        type leafref {
            path "/tinv:nodes/tinv:node/access-if/access-if-id";
        }
    }
    typedef pw-leafref {
        type leafref {
            path "/tinv:nodes/tinv:node/pw/pw-id";
        }
    }
    typedef mpls-if-leafref {
        type leafref {
            path "/tinv:nodes/tinv:node/mpls-if/mpls-if-id";
        }
    }
*/    
     grouping mpls-tp-delegated-service {
        list pw {
        	key "pw-id";
            leaf pw-id {
	            type mttypes:pw-id;
	            description "The unique identifier for the pw.";
	        }  
		    leaf pw-ref {
	            type mttypes:pw-ref;
	        }
        }
    }
    grouping mpls-tp-oam {

        leaf oam-enabler {
            type ttypes:enabler-type;
            description "The enabler of the oam.";
        }        
    	leaf oam-local-id {
        	type string;
        	description "The global unique oam identifier for tunnel oam.";
		}
		leaf oam-remote-id {
        	type string;
		}
		leaf oam-group-name {
        	type string;
       	 	description "The name of the oam group instance, global unique.";
		}
		leaf oam-message-interval-time {
        	type decimal64 {
        		fraction-digits 1;
        		range "3.3..1000";
        	}
		}
		leaf oam-type {
        	type ttypes:tunnel-oam-type;
  	  	 	description "The type of the oam.";
		}
	}
	grouping pw-oam {

        leaf oam-enabler {
            type ttypes:enabler-type;
            description "The enabler of the oam.";
        }        
    	leaf oam-local-id {
        	type string;
        	description "The global unique oam identifier for pw oam.";
		}
		leaf oam-remote-id {
        	type string;
		}
		leaf oam-group-name {
        	type string;
       	 	description "The name of the oam group instance, global unique.";
		}
		leaf oam-message-interval-time {
        	type decimal64 {
        		fraction-digits 1;
        		range "0..1000000";
        	}
		}
		leaf oam-type {
        	type ttypes:pw-oam-type;
  	  	 	description "The type of the pw oam.";
		}
	}
    grouping mpls-tp-path {
        leaf mpls-if-ref {
        	type mttypes:mpls-if-ref;
    	}
       	leaf path-status {
      		type ttunnel:tunnel-operational-status-type;
            description "The status of the path.";
  	    }
  	    leaf higher-tunnel-ref {
    		type ttunnel:tunnel-ref;
		}
	}
	grouping pw-path {
  	    leaf tunnel-ref {
    		type ttunnel:tunnel-ref;
		}
       	leaf path-status {
      		type ttunnel:tunnel-operational-status-type;
            description "The status of the path.";
  	    }
	}
    grouping mpls-tp-pw {

       leaf pw-id {
            type mttypes:pw-id;
            description "The unique identifier for the pw.";
        }
        leaf local-id {
            type string;
            description "The unique identifier in a particular local domain.";
        }        
        leaf name {
            type string;
            description "The name of the instance.";
        }
        leaf vpn-ref {
      		type mttypes:vpn-ref;
	   	}
        leaf pw-operational-status {
            type mttypes:pw-operational-status-type;
            description "The operational status of the pw.";
        }
        leaf pw-configuration-action {
            type mttypes:pw-configuration-action-type;
            description "The last configuration action of the pw.";
        }
        leaf pw-configuration-result {
            type ttypes:configuration-result-type;
            description "The configuration result of the action.";
        }     

		uses mttypes:mpls-tp-flow-qos;
		leaf deployment-enabler {
            type ttypes:enabler-type;
            description "The enabler of the deployment.";
        } 
		leaf deployment-status {
            type ttypes:deployment-status-type;
            description "The status of the deployment.";
        }		        
        leaf active-path-status {
            type ttypes:active-path-status-type;
            description "The status of the active path.";
        }      
        leaf end-node-ref {
            type tnode:node-ref;
        }
        leaf-list access-if-ref {
            type taccessif:access-if-ref;
        }        
        leaf service-type {
            type ttypes:service-type;
    		description "The type of the service.";
        }
        leaf service-ref {
            type ttypes:service-ref;
        }
   	
        container working-path {
			uses pw-path;
			uses mttypes:label-set;	
			uses pw-oam;	 
		}
		container protection-path {
			uses pw-path;			
			uses mttypes:label-set;	
			uses pw-oam;	 	 
		}
		container protection {
	    	leaf protection-type {
	        	type ttypes:pw-protection-type;
	  	    	description "The type of the protection.";
			}
			leaf protection-revert-type {
	        	type ttypes:pw-protection-revert-type;
	  	    	description "The type of the protection revert.";	        	
			}
			leaf protection-protocol-type {
	        	type ttypes:pw-protection-protocol-type;
	  	    	description "The type of the protection protocol.";
			}
			leaf protection-hold-off-time {
	        	type uint16;
			}
		}
    }    
    grouping mpls-tp-pw-xc {

       leaf pw-xc-id {
            type mttypes:pw-xc-id;
            description "The unique identifier for the pw xc.";
        }
        leaf local-id {
            type string;
            description "The unique identifier in a particular local domain.";
        }        
        leaf name {
            type string;
            description "The name of the instance.";
        }
        leaf pw-xc-operational-status {
            type mttypes:pw-xc-operational-status-type;
            description "The operational status of the pw cross-connect.";
        }
        leaf pw-xc-configuration-action {
            type mttypes:pw-xc-configuration-action-type;
            description "The last configuration action of the pw cross-connect.";
        }
        leaf pw-xc-configuration-result {
            type ttypes:configuration-result-type;
            description "The configuration result of the action.";
        }   
        uses mttypes:mpls-tp-flow-qos;
        leaf deployment-enabler {
            type ttypes:enabler-type;
            description "The enabler of the deployment.";
        } 
		leaf deployment-status {
            type ttypes:deployment-status-type;
            description "The status of the deployment.";
        }

        leaf src-node-ref {
            type tnode:node-ref;
        }       
        leaf dest-node-ref {
            type tnode:node-ref;
        } 
  
        container east-path {
        	uses pw-path;
        	uses mttypes:label-set;  
        }
        container west-path {
        	uses pw-path;
        	uses mttypes:label-set;  
        }
    	leaf protection-type {
        	type ttypes:pw-protection-type;
    		description "The type of the protection.";
    	}
    	leaf path-type {
            type ttypes:path-type;            
    		description "The type of the path.";
        }        
    	
    }    
    grouping mpls-tp-tunnel {

       leaf tunnel-id {
            type ttunnel:tunnel-id;
            description "The unique identifier for the tunnel.";
        }
        uses ttunnel:common-tunnel;
		uses mttypes:mpls-tp-flow-qos;
		        
        leaf active-path-status {
            type ttypes:active-path-status-type;
            description "The status of the active path.";
        }
      
        leaf src-node-ref {
            type tnode:node-ref;
        }       
        leaf dest-node-ref {
            type tnode:node-ref;
        }
        
        leaf-list service-ref {
            type ttypes:service-ref;
        }

    	container working-path {
			uses mpls-tp-path; 
			uses mttypes:label-set;	
			uses mpls-tp-oam;	 
    	}
    	container protection-path {
			uses mpls-tp-path; 
			uses mttypes:label-set;		 
			uses mpls-tp-oam;	 
    	} 
		container protection {
	    	leaf protection-type {
	        	type ttypes:tunnel-protection-type;
    			description "The type of the protection.";
			}
			leaf protection-revert-type {
	        	type ttypes:tunnel-protection-revert-type;
    			description "The type of the protection revert.";
			}
			leaf protection-protocol-type {
	        	type ttypes:tunnel-protection-protocol-type;
    			description "The type of the protection protocol.";
			}
			leaf protection-hold-off-time {
	        	type uint16;
			}
		}	
    }
    grouping mpls-tp-tunnel-xc {

       leaf tunnel-xc-id {
            type ttunnelxc:tunnel-xc-id;
            description "The unique identifier for the tunnel xc.";
        }
        uses ttunnelxc:common-tunnel-xc;
        uses mttypes:mpls-tp-flow-qos;
       
        leaf src-node-ref {
            type tnode:node-ref;
        }       
        leaf dest-node-ref {
            type tnode:node-ref;
        } 
        container east-path {
        	uses mpls-tp-path;
           	uses mttypes:label-set;
        }
        container west-path {
        	uses mpls-tp-path;
        	uses mttypes:label-set;		      	
        }
    	leaf protection-type {
        	type ttypes:tunnel-protection-type;
    		description "The type of the protection.";
    	}
    	leaf path-type {
            type ttypes:path-type;
    		description "The type of the path.";
        }        
    	
    }
    grouping mpls-tp-access-if {

       leaf access-if-id {
            type taccessif:access-if-id;
            description "The unique identifier for the access-if-id.";
        }
        uses taccessif:common-access-if;
        uses mttypes:mpls-tp-flow-qos;

        leaf service-type {
            type ttypes:service-type;
    		description "The type of the service.";
        }
        leaf service-ref {
            type ttypes:service-ref;
        }
        leaf vpn-ref {
      		type mttypes:vpn-ref;
	   	}
        leaf node-connector-ref {
            type tport:node-connector-ref;
        }
        
        list "constraint" {
            key "index";
         
            leaf index {
	            type ttypes:constraint-id;
	            description "The unique identifier for the constraint.";
        	}
			uses ttypes:common-constraint;
			leaf port-constraint-type {
            	type ttypes:port-constraint-type;
    			description "The type of the port constraint.";
        	}
        }
    }
    
    grouping mpls-tp-mpls-if {

       leaf mpls-if-id {
            type mttypes:mpls-if-id;
            description "The unique identifier for the mpls-if-id.";
        }
    	leaf local-id {
            type string;
            description "The unique identifier in a particular local domain.";
        }        
        leaf name {
            type string;
            description "The name of the instance.";
        }
        leaf mpls-if-operational-status {
            type mttypes:mpls-if-operational-status-type;
            description "The operational status of the mpls-if.";
        }
        leaf mpls-if-configuration-action {
            type mttypes:mpls-if-configuration-action-type;
            description "The last configuration action of the mpls-if.";
        }
        leaf mpls-if-configuration-result {
            type ttypes:configuration-result-type;
            description "The configuration result of the action.";
        }   
        uses mttypes:mpls-tp-flow-qos;
        leaf deployment-enabler {
            type ttypes:enabler-type;
            description "The enabler of the deployment.";
        } 
		leaf deployment-status {
            type ttypes:deployment-status-type;
            description "The status of the deployment.";
        } 
        
        leaf node-connector-ref {
            type tport:node-connector-ref;
        }        
        
        list "constraint" {
            key "index";
         
            leaf index {
	            type ttypes:constraint-id;
	            description "The unique identifier for the constraint.";
        	}
			uses ttypes:common-constraint;
			leaf port-constraint-type {
            	type ttypes:port-constraint-type;
    			description "The type of the port constraint.";
        	}
        }
    }
    grouping mpls-tp-vpn {

      leaf vpn-id {
        type mttypes:vpn-id;
        description "The unique identifier for the mpls-tp-vpn-id.";
      }  
    }
    grouping mpls-tp-node{
		list "tunnel" {
            key "tunnel-id";
            uses mpls-tp-tunnel;
        }
        list "mpls-if" {
            key "mpls-if-id";
            uses mpls-tp-mpls-if;
        }
        list "tunnel-xc" {
            key "tunnel-xc-id";
            uses mpls-tp-tunnel-xc;
        }
        list "access-if" {
            key "access-if-id";
            uses mpls-tp-access-if;
        }
        list "pw" {
            key "pw-id";
            uses mpls-tp-pw;
        }
        list "pw-xc" {
            key "pw-xc-id";
            uses mpls-tp-pw-xc;
        }
        list "vpn" {
            key "vpn-id";
            uses mpls-tp-vpn;
        }
        uses ttypes:switching-capacity;
    }

    grouping mpls-tp-node-connector {
        leaf mac-address {
    		type string;
    	} 
    }
   
    augment "/tinv:nodes/tinv:node" {
        ext:augment-identifier "mpls-tp-inventory-node";
        uses mpls-tp-node;
        
    }    
    augment "/tinv:nodes/tinv:node/tinv:node-connector" {
        ext:augment-identifier "mpls-tp-inventory-node-connector";
        uses mpls-tp-node-connector;
    }
   
    augment "/tinv:node-updated" {
        ext:augment-identifier "mpls-tp-inventory-node-updated";
		uses mpls-tp-node;
    }
    augment "/tinv:node-connector-updated" {
        ext:augment-identifier "mpls-tp-inventory-node-connector-updated";
        uses mpls-tp-node-connector;
    }
    
    augment "/tinv:tunnel-updated" {
        ext:augment-identifier "mpls-tp-inventory-tunnel-updated";
		uses mpls-tp-tunnel;
    }
    augment "/tinv:tunnel-xc-updated" {
        ext:augment-identifier "mpls-tp-inventory-tunnel-xc-updated";
		uses mpls-tp-tunnel-xc;
    }
    augment "/tinv:access-if-updated" {
        ext:augment-identifier "mpls-tp-inventory-access-if-updated";
		uses mpls-tp-access-if;
    }
    augment "/tinv:delegated-service-updated" {
        ext:augment-identifier "mpls-tp-inventory-delegated-service-updated";
		uses mpls-tp-delegated-service;
    }
    augment "/tinv:complete-path-set-provision-service-updated" {
        ext:augment-identifier "mpls-tp-inventory-complete-path-set-provision-service-updated";
		uses mpls-tp-delegated-service;
    }
/*    
    augment "/tinv:tunnel-removed" {
        ext:augment-identifier "mpls-tp-inventory-tunnel-removed";
		leaf tunnel-id {
            type ttunnel:tunnel-id;
            description "The unique identifier for the tunnel.";
        }
    }
    augment "/tinv:tunnel-xc-removed" {
        ext:augment-identifier "mpls-tp-inventory-tunnel-xc-removed";
		leaf tunnel-xc-id {
            type ttunnelxc:tunnel-xc-id;
            description "The unique identifier for the tunnel xc.";
        }
    }
    augment "/tinv:access-if-removed" {
        ext:augment-identifier "mpls-tp-inventory-access-if-removed";
		leaf access-if-id {
            type taccessif:access-if-id;
            description "The unique identifier for the access-if-id.";
        }
    }
    augment "/tinv:delegated-service-removed" {
        ext:augment-identifier "mpls-tp-inventory-delegated-service-removed";
	  	leaf service-id {
        	type ttypes:service-id;
    	}
    }    
*/    
    augment "/tinv:set-tunnel/tinv:input" {
        ext:augment-identifier "mpls-tp-set-tunnel-input";
		uses mtprov:mpls-tp-tunnel-provision;
    }
    augment "/tinv:set-tunnel-xc/tinv:input" {
        ext:augment-identifier "mpls-tp-set-tunnel-xc-input";
		uses mtprov:mpls-tp-tunnel-xc-provision;
    }
    augment "/tinv:set-access-if/tinv:input" {
        ext:augment-identifier "mpls-tp-set-access-if-input";
		uses mtprov:mpls-tp-access-if-provision;
    }
    
    augment "/tinv:set-delegated-service/tinv:input" {
        ext:augment-identifier "mpls-tp-set-delegated-service-input";
		uses mtprov:mpls-tp-service-provision;
    }
    augment "/tinv:set-complete-path-set-provision-service/tinv:input" {
        ext:augment-identifier "mpls-tp-set-complete-path-set-provision-service-input";
		uses mtprov:mpls-tp-complete-path-set-provision-service-provision;
    }
    
    augment "/tinv:update-tunnel/tinv:input" {
        ext:augment-identifier "mpls-tp-update-tunnel-input";
		uses mtprov:mpls-tp-tunnel-provision;
    }
    augment "/tinv:update-tunnel-xc/tinv:input" {
        ext:augment-identifier "mpls-tp-update-tunnel-xc-input";
		uses mtprov:mpls-tp-tunnel-xc-provision;
    }
    augment "/tinv:update-access-if/tinv:input" {
        ext:augment-identifier "mpls-tp-update-access-if-input";
		uses mtprov:mpls-tp-access-if-provision;
    }
    
    augment "/tinv:update-delegated-service/tinv:input" {
        ext:augment-identifier "mpls-tp-update-delegated-service-input";
		uses mtprov:mpls-tp-service-provision;
    }
    augment "/tinv:update-complete-path-set-provision-service/tinv:input" {
        ext:augment-identifier "mpls-tp-update-complete-path-set-provision-service-input";
		uses mtprov:mpls-tp-complete-path-set-provision-service-provision;
    }

    augment "/tinv:get-node/tinv:output" {
        ext:augment-identifier "mpls-tp-get-node-output";
		uses mpls-tp-node;
    }    
    augment "/tinv:get-tunnel/tinv:output" {
        ext:augment-identifier "mpls-tp-get-tunnel-output";
		uses mpls-tp-tunnel;
    }
    augment "/tinv:get-tunnel-xc/tinv:output" {
        ext:augment-identifier "mpls-tp-get-tunnel-xc-output";
		uses mpls-tp-tunnel-xc;
    }
    augment "/tinv:get-access-if/tinv:output" {
        ext:augment-identifier "mpls-tp-get-access-if-output";
		uses mpls-tp-access-if;
    }
    
    augment "/tinv:get-delegated-service/tinv:output" {
        ext:augment-identifier "mpls-tp-get-delegated-service-output";
		uses mpls-tp-delegated-service;
    }
    augment "/tinv:get-complete-path-set-provision-service/tinv:output" {
        ext:augment-identifier "mpls-tp-get-complete-path-set-provision-service-output";
		uses mpls-tp-delegated-service;
    }
    
    
   
    rpc set-pw {
    	description "set the pw";
    	input {
    		leaf node-ref {
            	ext:context-reference tnode:node-context;
            	type tnode:node-ref;
        	}
        	leaf service-id {
            	type ttypes:service-id;
            	description "The unique identifier for the service.";
        	}
        	uses mtprov:mpls-tp-pw-provision;
    	}
    	output {
	  	    leaf response {
	  	    	type ttypes:response-type;
    			description "The type of the response.";
	  	   	}
		  	leaf reason {
	            type string;
	        }
    	}
    } 
    rpc set-pw-xc {
    	description "set the pw cross-connect";
    	input {
    		leaf node-ref {
            	ext:context-reference tnode:node-context;
            	type tnode:node-ref;
        	}
        	leaf service-id {
            	type ttypes:service-id;
            	description "The unique identifier for the service.";
        	}
        	uses mtprov:mpls-tp-pw-xc-provision;
	   	}
    	output {
	  	    leaf response {
	  	    	type ttypes:response-type;
	  	    	description "The type of the response.";
	  	   	}
		  	leaf reason {
	            type string;
	        }
    	}
    }
    rpc set-mpls-if {
    	description "set the mpls if";
    	input {
    		leaf node-ref {
            	ext:context-reference tnode:node-context;
            	type tnode:node-ref;
        	}
        	leaf service-id {
            	type ttypes:service-id;
            	description "The unique identifier for the service.";
        	}
        	uses mtprov:mpls-tp-mpls-if-provision;
	   	}
    	output {
	  	    leaf response {
	  	    	type ttypes:response-type;
	  	    	description "The type of the response.";
	  	   	}
		  	leaf reason {
	            type string;
	        }
    	}
    }
    rpc set-vpn {
    	description "set the vpn";
    	input {
    		leaf node-ref {
            	ext:context-reference tnode:node-context;
            	type tnode:node-ref;
        	}
        	leaf service-id {
            	type ttypes:service-id;
            	description "The unique identifier for the service.";
        	}
        	uses mtprov:mpls-tp-vpn-provision;
	   	}
    	output {
	  	    leaf response {
	  	    	type ttypes:response-type;
	  	    	description "The type of the response.";
	  	   	}
		  	leaf reason {
	            type string;
	        }
    	}
    }
    rpc update-pw {
    	description "update the pw";
    	input {
    		leaf node-ref {
            	ext:context-reference tnode:node-context;
            	type tnode:node-ref;
        	}
        	leaf service-id {
            	type ttypes:service-id;
            	description "The unique identifier for the service.";
        	}
        	uses mtprov:mpls-tp-pw-provision;
    	}
    	output {
	  	    leaf response {
	  	    	type ttypes:response-type;
	  	    	description "The type of the response.";
	  	   	}
		  	leaf reason {
	            type string;
	        }
    	}
    } 
    rpc update-pw-xc {
    	description "update the pw cross-connect";
    	input {
    		leaf node-ref {
            	ext:context-reference tnode:node-context;
            	type tnode:node-ref;
        	}
        	leaf service-id {
            	type ttypes:service-id;
            	description "The unique identifier for the service.";
        	}
        	uses mtprov:mpls-tp-pw-xc-provision;
	   	}
    	output {
	  	    leaf response {
	  	    	type ttypes:response-type;
	  	    	description "The type of the response.";
	  	   	}
		  	leaf reason {
	            type string;
	        }
    	}
    }
    rpc update-mpls-if {
    	description "update the mpls if";
    	input {
    		leaf node-ref {
            	ext:context-reference tnode:node-context;
            	type tnode:node-ref;
        	}
        	leaf service-id {
            	type ttypes:service-id;
            	description "The unique identifier for the service.";
        	}
        	uses mtprov:mpls-tp-mpls-if-provision;
	   	}
    	output {
	  	    leaf response {
	  	    	type ttypes:response-type;
	  	    	description "The type of the response.";
	  	   	}
		  	leaf reason {
	            type string;
	        }
    	}
    } 
    rpc update-vpn {
    	description "update the vpn";
    	input {
    		leaf node-ref {
            	ext:context-reference tnode:node-context;
            	type tnode:node-ref;
        	}
        	leaf service-id {
            	type ttypes:service-id;
            	description "The unique identifier for the service.";
        	}
        	uses mtprov:mpls-tp-vpn-provision;
	   	}
    	output {
	  	    leaf response {
	  	    	type ttypes:response-type;
	  	    	description "The type of the response.";
	  	   	}
		  	leaf reason {
	            type string;
	        }
    	}
    } 
    rpc get-pw {
    	description "get information of the pw";
    	input {
    		leaf node-ref {
            	ext:context-reference tnode:node-context;
            	type tnode:node-ref;
        	}
    	    leaf pw-id {
 	           type mttypes:pw-id;
            	description "The unique identifier for the pw.";
    	    }
    	}
    	output {
	  	    leaf response {
	  	    	type ttypes:response-type;
	  	    	description "The type of the response.";
	  	   	}
		  	leaf reason {
	            type string;
	        }
	  	   	uses mpls-tp-pw;
    	}
    } 
    rpc get-pw-xc {
    	description "get information of the pw cross-connect";
    	input {
    		leaf node-ref {
            	ext:context-reference tnode:node-context;
            	type tnode:node-ref;
        	}
    	    leaf pw-xc-id {
 	           type mttypes:pw-xc-id;
            	description "The unique identifier for the pw cross-connect.";
    	    }
    	}
    	output {
	  	    leaf response {
	  	    	type ttypes:response-type;
	  	    	description "The type of the response.";
	  	   	}
		  	leaf reason {
	            type string;
	        }
	  	   	uses mpls-tp-pw-xc;
    	}
    } 
    rpc get-mpls-if {
    	description "get information of the mpls if";
    	input {
    		leaf node-ref {
            	ext:context-reference tnode:node-context;
            	type tnode:node-ref;
        	}
    	    leaf mpls-if-id {
 	           type mttypes:mpls-if-id;
            	description "The unique identifier for the mpls if.";
    	    }
    	}
    	output {
	  	    leaf response {
	  	    	type ttypes:response-type;
	  	    	description "The type of the response.";
	  	   	}
		  	leaf reason {
	            type string;
	        }
	  	   	uses mpls-tp-mpls-if;
    	}
    }
    rpc get-vpn {
    	description "get information of the vpn";
    	input {
    		leaf node-ref {
            	ext:context-reference tnode:node-context;
            	type tnode:node-ref;
        	}
    	    leaf vpn-id {
 	           type uint16;
            	description "The unique identifier for the vpn.";
    	    }
    	}
    	output {
	  	    leaf response {
	  	    	type ttypes:response-type;
	  	    	description "The type of the response.";
	  	   	}
		  	leaf reason {
	            type string;
	        }
	  	   	uses mpls-tp-vpn;
    	}
    }
    rpc delete-pw {
    	description "delete the pw";
    	input {
    		leaf node-ref {
            	ext:context-reference tnode:node-context;
            	type tnode:node-ref;
        	}
    	    leaf pw-id {
 	           type mttypes:pw-id;
            	description "The unique identifier for the pw.";
    	    }
    	}
    	output {
	  	    leaf response {
	  	    	type ttypes:response-type;
	  	    	description "The type of the response.";
	  	   	}
		  	leaf reason {
	            type string;
	        }
    	}
    } 
    rpc delete-pw-xc {
    	description "delete the pw cross-connect";
    	input {
    		leaf node-ref {
            	ext:context-reference tnode:node-context;
            	type tnode:node-ref;
        	}
    	    leaf pw-xc-id {
 	           type mttypes:pw-xc-id;
            	description "The unique identifier for the pw cross-connect.";
    	    }
    	}
    	output {
	  	    leaf response {
	  	    	type ttypes:response-type;
	  	    	description "The type of the response.";
	  	   	}
		  	leaf reason {
	            type string;
	        }
    	}
    } 
    rpc delete-mpls-if {
    	description "delete the mpls if";
    	input {
    		leaf node-ref {
            	ext:context-reference tnode:node-context;
            	type tnode:node-ref;
        	}
    	    leaf mpls-if-id {
 	           type mttypes:mpls-if-id;
            	description "The unique identifier for the mpls if.";
    	    }
    	}
    	output {
	  	    leaf response {
	  	    	type ttypes:response-type;
	  	    	description "The type of the response.";
	  	   	}
		  	leaf reason {
	            type string;
	        }
    	}
    }
    rpc delete-vpn {
    	description "delete the vpn";
    	input {
    		leaf node-ref {
            	ext:context-reference tnode:node-context;
            	type tnode:node-ref;
        	}
    	    leaf vpn-id {
 	           type uint16;
            	description "The unique identifier for the vpn.";
    	    }
    	}
    	output {
	  	    leaf response {
	  	    	type ttypes:response-type;
	  	    	description "The type of the response.";
	  	   	}
		  	leaf reason {
	            type string;
	        }
    	}
    }
    notification pw-updated {
		description "describes that something on the pw has been updated";
        leaf node-ref {
            ext:context-reference tnode:node-context;
            type tnode:node-ref;
        }
        leaf service-id {
            type ttypes:service-id;
           	description "The unique identifier for the service.";
        }
        uses mpls-tp-pw;
    }
    notification pw-removed {
    	description "describes that the pw has been removed";
        leaf node-ref {
            ext:context-reference tnode:node-context;
            type tnode:node-ref;
        }
        leaf pw-id {
            type mttypes:pw-id;
            description "The unique identifier for the pw.";
        }
    }
    notification pw-xc-updated {
		description "describes that something on the pw cross-connect has been updated";
        leaf node-ref {
            ext:context-reference tnode:node-context;
            type tnode:node-ref;
        }
        leaf service-id {
            type ttypes:service-id;
           	description "The unique identifier for the service.";
        }
        uses mpls-tp-pw-xc;
    }
    notification pw-xc-removed {
    	description "describes that the pw cross-connect has been removed";
        leaf node-ref {
            ext:context-reference tnode:node-context;
            type tnode:node-ref;
        }
        leaf pw-xc-id {
            type mttypes:pw-xc-id;
            description "The unique identifier for the pw xc.";
        }
    }
    notification mpls-if-updated {
		description "describes that something on the mpls-if has been updated";
        leaf node-ref {
            ext:context-reference tnode:node-context;
            type tnode:node-ref;
        }
        leaf service-id {
            type ttypes:service-id;
           	description "The unique identifier for the service.";
        }
        uses mpls-tp-mpls-if;
    }
    notification mpls-if-removed {
    	description "describes that the mpls if has been removed";
        leaf node-ref {
            ext:context-reference tnode:node-context;
            type tnode:node-ref;
        }
        leaf mpls-if-id {
            type mttypes:mpls-if-id;
            description "The unique identifier for the mpls-if-id.";
        }
    }
    notification vpn-updated {
		description "describes that something on the vpn has been updated";
        leaf node-ref {
            ext:context-reference tnode:node-context;
            type tnode:node-ref;
        }
        leaf service-id {
            type ttypes:service-id;
           	description "The unique identifier for the service.";
        }
        uses mpls-tp-vpn;
    }
    notification vpn-removed {
    	description "describes that the vpn has been removed";
        leaf node-ref {
            ext:context-reference tnode:node-context;
            type tnode:node-ref;
        }
        leaf vpn-id {
            type mttypes:vpn-id;
            description "The unique identifier for the vpn-id.";
        }
    }
 
}
